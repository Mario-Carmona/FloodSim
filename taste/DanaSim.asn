DANASIM-DATAVIEW DEFINITIONS ::=
BEGIN

    /* ================================ */
    /* DEFINITION OF DATA TYPES         */
    /* ================================ */

    T-UInt32 ::= INTEGER (0 .. 4294967294)

    T-Float ::= REAL (-2147483648.0 .. 2147483647.0)

    FolderPath ::= IA5String (SIZE(1..255))

    /* Synchronization Mode */
    SyncMode ::= ENUMERATED {
        realTimeSkipFrames,
        losslessAllFrames
    }

    /* Simulation Settings */
    SimConfig ::= SEQUENCE {
        gisDataPath FolderPath,
        totalDuration T-Float,
        timeStep T-Float,
        snapshotFreq T-UInt32,
        mode SyncMode
    }

    /* Data Matrix */
    Layer ::= SEQUENCE SIZE (1 .. 1048576) OF T-Float

    /* State of the Automata with Visible Layers */
    CellularAutomatonState ::= SEQUENCE {
        rows INTEGER (1 .. 1024),
        cols INTEGER (1 .. 1024),
        timestamp T-Float,
        stepIndex T-UInt32,

        /* Explicit layers */
        elevation Layer,
        waterDepth Layer
    }




    -----------



    SurfaceType ::= ENUMERATED {
        soil(0),
        rock(1),
        asphalt(2),
        forest(3),
        waterSurface(4)
    }

    CellType ::= ENUMERATED {
        normal(0),
        source(1),
        sink(2)
    }

END
