Core-Datamodel DEFINITIONS ::=
BEGIN
--  This file was generated automatically by OpenGEODE
IMPORTS
   T-UInt32, T-UInt64, Double, SurfaceType, CellType, FrictionCoefficient, ScaleFactor, Duration, TimeStep, FilePath, CellState, GridVector, Grid, CellIndex, Outflow, OutflowList, MooreNeighborIndex, MooreNeighborList, GridCellNeighborList, FlowingWaterEvent, FlowingWaterEventList, GridModification, GridModificationList FROM DANASIM-DATAVIEW
   T-Int32, TASTE-BasicTypes-T-UInt32, T-Int8, T-UInt8, T-Boolean, T-Null-Record, T-Runtime-Error FROM TASTE-BasicTypes
   PID-Range, PID FROM System-Dataview;

Core-States ::= ENUMERATED {idle, running}

Core-Context ::= SEQUENCE {
   state Core-States,
   init-done BOOLEAN,
   sender PID,
   offspring PID,
   currenttimestep TimeStep,
   totaltimesteps TimeStep,
   coregrid Grid,
   flowingwatereventlist FlowingWaterEventList,
   coresnapshotperiod TimeStep,
   nextsnapshottimestep TimeStep,
   finished T-Boolean,
   accummodlist GridModificationList,
   gridneighbors GridCellNeighborList
}

Core-T-Runtime-Error-Selection ::= ENUMERATED {noerror-present(1), encodeerror-present(2), decodeerror-present(3)}
END
