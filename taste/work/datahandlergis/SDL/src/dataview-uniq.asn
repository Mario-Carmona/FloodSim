DANASIM-DATAVIEW DEFINITIONS ::=
BEGIN

    Double ::= REAL (0.0 .. 1.0E308)

    FolderPath ::= IA5String (SIZE(1..255))

    FilePath ::= IA5String (SIZE(1..255))

    -- Defines the state of water movement in a cell (Layer 3).
    WaterState ::= ENUMERATED {
        noMovement (0),
        inMovement (1)
    }

    -- Structure defining the three state layers for a single Cellular Automaton cell.
    CellLayerData ::= SEQUENCE {
        elevation      Double,     -- Layer 1: Terrain elevation (m) - Typically constant.
        waterHeight    Double,     -- Layer 2: Current water height (m) - Evolves based on flow.
        waterState     WaterState  -- Layer 3: Water movement status - Evolves based on net flow.
    }

    -- Type representing the entire map or grid (GridData signal).
    -- It is an array (SEQUENCE OF) of all the CellLayerData instances.
    -- The size (N x N) is defined by the simulation context, here specified as 1 to MAX.
    GridData ::= SEQUENCE SIZE (1 .. 1048576) OF CellLayerData

    --------------------------




    T-UInt32 ::= INTEGER (0 .. 4294967294)

    T-UInt64 ::= INTEGER (0 .. 18446744073709551615)



    SurfaceType ::= ENUMERATED {
        soil(0),
        rock(1),
        asphalt(2),
        forest(3),
        waterSurface(4)
    }

    CellType ::= ENUMERATED {
        normal(0),
        source(1),
        sink(2)
    }

    FrictionCoefficient ::= REAL (0.0 .. 1.0)

    ScaleFactor ::= REAL (0.0 .. 8.0)

    Duration ::= T-UInt32  -- unit: seconds

    TimeStep ::= T-UInt32

    CellState ::= SEQUENCE {
        elevation   T-UInt32,  -- unit: mm - range: [sea level, mount everest]
        waterDepth  T-UInt32,    -- unit: mm - range: [0 m, 10 m]
        surfaceType SurfaceType,
        cellType CellType,
        inflowPerTimeStep T-UInt32 OPTIONAL
    }

    GridVector ::= SEQUENCE (SIZE(1 .. 1048576)) OF CellState

    Grid ::= SEQUENCE {
        width  INTEGER (1 .. 1024),
        height INTEGER (1 .. 1024),
        cellSize Double,  -- unit: m
        cellArea Double,  -- unit: m^2
        cells  GridVector
    }

    CellIndex ::= INTEGER (0 .. 1048575)

    Outflow ::= SEQUENCE {
        depth    T-UInt32,
        neighbor CellIndex
    }

    OutflowList ::= SEQUENCE (SIZE(0 .. 9)) OF Outflow

    MooreNeighborIndex ::= INTEGER (0 .. 8)

    MooreNeighborList ::= SEQUENCE (SIZE(0 .. 9)) OF CellIndex

    GridCellNeighborList ::= SEQUENCE (SIZE(0 .. 1048576)) OF MooreNeighborList

    FlowingWaterEvent ::= SEQUENCE {
        targetCell CellIndex
    }

    FlowingWaterEventList ::= SEQUENCE (SIZE(0 .. 1048576)) OF FlowingWaterEvent

    GridModification ::= SEQUENCE {
        targetCell CellIndex,
        increment  BOOLEAN,
        delta      T-UInt32
    }

    GridModificationList ::= SEQUENCE (SIZE(0 .. 4294967295)) OF GridModification

END

TASTE-BasicTypes DEFINITIONS ::=
BEGIN

-- Set of TASTE predefined basic types

T-Int32 ::=  INTEGER (-2147483648 .. 2147483647)

T-UInt32 ::= INTEGER (0 .. 4294967294)

T-Int8 ::= INTEGER (-128 .. 127)

T-UInt8 ::= INTEGER (0 .. 255)

T-Boolean ::= BOOLEAN

T-Null-Record ::= SEQUENCE {}

T-Runtime-Error ::= CHOICE {
   noerror T-UInt32, -- this shall be NULL, but DMT does not support NULL and SEDS does not support empty sequences
   encodeerror T-Int32, -- the names shall be changed after fix in seds converter (space creator) will be merged
   decodeerror T-Int32
}

END


-- Dataview generated on-the-fly providing information on the system
-- and made available to the user code.
System-Dataview DEFINITIONS ::=
BEGIN

   -- Range of PID - type can be used to size arrays of PID type
   PID-Range ::= INTEGER(0..4)

   -- List of functions (instances) present in the system
   PID ::= ENUMERATED {
       coreengineca,
       
       datahandlergis,
       
       function-6,
       
       userinterface,
       
       
       env
   }

END
