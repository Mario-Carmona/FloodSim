DANASIM-DATAVIEW DEFINITIONS ::=
BEGIN

    T-UInt32 ::= INTEGER (0 .. 4294967294)

    SurfaceType ::= ENUMERATED {
        soil,
        rock,
        asphalt,
        forest,
        waterSurface
    }

    FlowCoefficient ::= REAL (0.0 .. 1.0)

    ScaleFactor ::= REAL (0.0 .. 8.0)

    Duration ::= T-UInt32  -- unit: seconds

    TimeStep ::= T-UInt32

    FilePath ::= IA5String (SIZE(1..255))

    CellState ::= SEQUENCE {
        elevation   T-UInt32,  -- unit: mm - range: [sea level, mount everest]
        waterDepth  T-UInt32,    -- unit: mm - range: [0 m, 10 m]
        surfaceType SurfaceType
    }

    Height ::= T-UInt32

    GridVector ::= SEQUENCE (SIZE(1 .. 1048576)) OF CellState

    Grid ::= SEQUENCE {
        width  INTEGER (1 .. 1024),
        height INTEGER (1 .. 1024),
        cells  GridVector
    }

    CellIndex ::= INTEGER (0 .. 1048575)

    Outflow ::= SEQUENCE {
        depth    T-UInt32,
        neighbor CellIndex
    }

    OutflowList ::= SEQUENCE (SIZE(0 .. 9)) OF Outflow

    MooreNeighborIndex ::= INTEGER (0 .. 8)

    MooreNeighborList ::= SEQUENCE (SIZE(0 .. 9)) OF CellIndex

    GridCellNeighborList ::= SEQUENCE (SIZE(0 .. 1048576)) OF MooreNeighborList

    FlowingWaterEvent ::= SEQUENCE {
        targetCell CellIndex
    }

    FlowingWaterEventList ::= SEQUENCE (SIZE(0 .. 1048576)) OF FlowingWaterEvent

    GridModification ::= SEQUENCE {
        targetCell CellIndex,
        increment  BOOLEAN,
        delta      T-UInt32
    }

    GridModificationList ::= SEQUENCE (SIZE(0 .. 4294967295)) OF GridModification

END

TASTE-BasicTypes DEFINITIONS ::=
BEGIN

-- Set of TASTE predefined basic types

T-Int32 ::=  INTEGER (-2147483648 .. 2147483647)

T-UInt32 ::= INTEGER (0 .. 4294967294)

T-Int8 ::= INTEGER (-128 .. 127)

T-UInt8 ::= INTEGER (0 .. 255)

T-Boolean ::= BOOLEAN

T-Null-Record ::= SEQUENCE {}

T-Runtime-Error ::= CHOICE {
   noerror T-UInt32, -- this shall be NULL, but DMT does not support NULL and SEDS does not support empty sequences
   encodeerror T-Int32, -- the names shall be changed after fix in seds converter (space creator) will be merged
   decodeerror T-Int32
}

END


-- Dataview generated on-the-fly providing information on the system
-- and made available to the user code.
System-Dataview DEFINITIONS ::=
BEGIN

   -- Range of PID - type can be used to size arrays of PID type
   PID-Range ::= INTEGER(0..3)

   -- List of functions (instances) present in the system
   PID ::= ENUMERATED {
       core,
       
       io-gis,
       
       ui,
       
       
       env
   }

END
