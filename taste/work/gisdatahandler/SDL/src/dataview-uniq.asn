DANASIM-DATAVIEW DEFINITIONS ::=
BEGIN

    /* ================================ */
    /* DEFINITION OF DATA TYPES         */
    /* ================================ */

    T-UInt32 ::= INTEGER (0 .. 4294967294)

    T-Float ::= REAL (-2147483648.0 .. 2147483647.0)

    FolderPath ::= IA5String (SIZE(1..255))

    /* Synchronization Mode */
    SyncMode ::= ENUMERATED {
        realTimeSkipFrames,
        losslessAllFrames
    }

    /* Simulation Settings */
    SimConfig ::= SEQUENCE {
        gisDataPath FolderPath,
        totalDuration T-Float,
        timeStep T-Float,
        snapshotFreq T-UInt32,
        mode SyncMode
    }

    /* Data Matrix */
    Layer ::= SEQUENCE SIZE (1 .. 1048576) OF T-Float

    /* State of the Automata with Visible Layers */
    CellularAutomatonState ::= SEQUENCE {
        rows INTEGER (1 .. 1024),
        cols INTEGER (1 .. 1024),
        timestamp T-Float,
        stepIndex T-UInt32,

        /* Explicit layers */
        elevation Layer,
        waterDepth Layer
    }




    -----------



    SurfaceType ::= ENUMERATED {
        soil(0),
        rock(1),
        asphalt(2),
        forest(3),
        waterSurface(4)
    }

    CellType ::= ENUMERATED {
        normal(0),
        source(1),
        sink(2)
    }

END

TASTE-BasicTypes DEFINITIONS ::=
BEGIN

-- Set of TASTE predefined basic types

T-Int32 ::=  INTEGER (-2147483648 .. 2147483647)

T-UInt32 ::= INTEGER (0 .. 4294967294)

T-Int8 ::= INTEGER (-128 .. 127)

T-UInt8 ::= INTEGER (0 .. 255)

T-Boolean ::= BOOLEAN

T-Null-Record ::= SEQUENCE {}

T-Runtime-Error ::= CHOICE {
   noerror T-UInt32, -- this shall be NULL, but DMT does not support NULL and SEDS does not support empty sequences
   encodeerror T-Int32, -- the names shall be changed after fix in seds converter (space creator) will be merged
   decodeerror T-Int32
}

END


-- Dataview generated on-the-fly providing information on the system
-- and made available to the user code.
System-Dataview DEFINITIONS ::=
BEGIN

   -- Range of PID - type can be used to size arrays of PID type
   PID-Range ::= INTEGER(0..3)

   -- List of functions (instances) present in the system
   PID ::= ENUMERATED {
       coreengineca,
       
       gisdatahandler,
       
       userinterface,
       
       
       env
   }

END
