Io-gis-Datamodel DEFINITIONS ::=
BEGIN
--  This file was generated automatically by OpenGEODE
IMPORTS
   T-UInt32, SurfaceType, CellType, FlowCoefficient, ScaleFactor, Duration, TimeStep, FilePath, CellState, Height, GridVector, Grid, CellIndex, Outflow, OutflowList, MooreNeighborIndex, MooreNeighborList, GridCellNeighborList, FlowingWaterEvent, FlowingWaterEventList, GridModification, GridModificationList FROM DANASIM-DATAVIEW
   T-Int32, TASTE-BasicTypes-T-UInt32, T-Int8, T-UInt8, T-Boolean, T-Null-Record, T-Runtime-Error FROM TASTE-BasicTypes
   PID-Range, PID FROM System-Dataview;

Io-gis-States ::= ENUMERATED {idle}

Io-gis-Context ::= SEQUENCE {
   state Io-gis-States,
   init-done BOOLEAN,
   sender PID,
   offspring PID
}

Io-Gis-T-Runtime-Error-Selection ::= ENUMERATED {noerror-present(1), encodeerror-present(2), decodeerror-present(3)}
END
