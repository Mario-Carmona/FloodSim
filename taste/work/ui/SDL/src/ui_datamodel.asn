Ui-Datamodel DEFINITIONS ::=
BEGIN
--  This file was generated automatically by OpenGEODE
IMPORTS
   T-Real32, T-UReal32, SurfaceType, WaterState, Elevation, WaterVolume, Duration, TimeStep, FilePath, GridWidth, GridHeight, CellState, GridVector, Grid, CellIndex, NeighborList, GridCellNeighborList, WaterIncrementEventList, GridModification, GridModificationList FROM DANASIM-DATAVIEW
   T-Int32, T-UInt32, T-Int8, T-UInt8, T-Boolean, T-Null-Record, T-Runtime-Error FROM TASTE-BasicTypes
   PID-Range, PID FROM System-Dataview;

Ui-States ::= ENUMERATED {waitingsnapshots, waitinginitialgrid}

Ui-Context ::= SEQUENCE {
   state Ui-States,
   init-done BOOLEAN,
   sender PID,
   offspring PID,
   folder FilePath,
   timestepduration Duration,
   totalduration Duration,
   snapshotperiod TimeStep,
   uigrid Grid,
   uifinished T-Boolean
}

Ui-T-Runtime-Error-Selection ::= ENUMERATED {noerror-present(1), encodeerror-present(2), decodeerror-present(3)}
END
