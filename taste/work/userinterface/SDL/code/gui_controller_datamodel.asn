Gui-controller-Datamodel DEFINITIONS ::=
BEGIN
--  This file was generated automatically by OpenGEODE
IMPORTS
   T-UInt32, T-Float, FolderPath, SimConfig, Layer, CellularAutomatonState, SurfaceType, CellType FROM DANASIM-DATAVIEW
   T-Int32, TASTE-BasicTypes-T-UInt32, T-Int8, T-UInt8, T-Boolean, T-Null-Record, T-Runtime-Error FROM TASTE-BasicTypes
   PID-Range, PID FROM System-Dataview;

Gui-controller-States ::= ENUMERATED {idle}

Gui-controller-Context ::= SEQUENCE {
   state Gui-controller-States,
   init-done BOOLEAN,
   sender PID,
   offspring PID,
   cfg SimConfig,
   visiblestate CellularAutomatonState
}

Gui-Controller-T-Runtime-Error-Selection ::= ENUMERATED {noerror-present(1), encodeerror-present(2), decodeerror-present(3)}
Gui-Controller-T-Runtime-Error-Selection ::= ENUMERATED {noerror-present(1), encodeerror-present(2), decodeerror-present(3)}
END
